-- SPDX-License-Identifier: Apache-2.0
-- Copyright (C) 2008-2022 OKTET Labs Ltd. All rights reserved.


TE-NDN-Platform
DEFINITIONS ::=
BEGIN

IMPORTS DATA-UNIT FROM TE-NDN-General;


EXPORTS ;

Conn-Layer-eth-if-up-param ::= SEQUENCE {
    vlan-id         INTEGER,
    priority        INTEGER (0..7)
}

Conn-Layer-eth-if ::= SEQUENCE {
    up-param        Conn-Layer-eth-if-up-param,
    param           NULL
}

Conn-Layer-eth-port ::= SEQUENCE {
    up-param        NULL,
    param           NULL
}

Conn-Layer-firewall-param ::= SEQUENCE {
    firewall        BOOLEAN,
    nat             BOOLEAN,
    dmz             BOOLEAN,
    dmz-host        OCTET STRING,
    enforce-mss     BOOLEAN
}

Conn-Layer-firewall ::= SEQUENCE {
    up-param        NULL,
    param           Conn-Layer-firewall-param
}

Conn-Layer-ip-dhcp-up-param ::= SEQUENCE {
    vendorid        UniversalString,
    clientid        UniversalString,
    hostname        UniversalString
}

Conn-Layer-ip-dhcp ::= SEQUENCE {
    up-param        Conn-Layer-ip-dhcp-up-param,
    param           NULL
}

Conn-Layer-ip-ipcp ::= SEQUENCE {
    up-param        NULL,
    param           NULL
}

Conn-Layer-ip-static-param ::= SEQUENCE {
    addr            OCTET STRING,
    prefix          INTEGER (0..32),
    gateway         OCTET STRING,
    hostname        UniversalString,
    domain          UniversalString,
    dns1            OCTET STRING,
    dns2            OCTET STRING,
    dns3            OCTET STRING
}

Conn-Layer-ip-static ::= SEQUENCE {
    up-param        NULL,
    param           Conn-Layer-ip-static-param
}

Conn-Layer-ppp-param ::= SEQUENCE {
    username        UniversalString,
    password        UniversalString,
    service-name    UniversalString,
    ac-name         UniversalString,
    auth-type       UniversalString,
    mru             INTEGER (0..65535),
    persist         BOOLEAN,
    maxfail         INTEGER (0..65535),
    demand          BOOLEAN,
    idle            INTEGER (0..65535),
    proxyarp        BOOLEAN,
    debug           BOOLEAN,
    keepalive-retry INTEGER (0..65535),
    keepalive-inteval   INTEGER (0..65535)
}

Conn-Layer-ppp ::= SEQUENCE {
    up-param        NULL,
    param           Conn-Layer-ppp-param
}


Conn-Type-Enum ::= INTEGER {
    static(0),
    dhcp(1),
    pppoe(2),
    ...
}

Service-Separation-Enum ::= INTEGER {
    none(0),
    primary(1),
    secondary(2),
    tertiary(3),
    quaternary(4),
    quinary(5)
}

Service-Separation ::= SEQUENCE {
    default     Service-Separation-Enum,
    management  Service-Separation-Enum,
    voice       Service-Separation-Enum
}

Connection-Item ::= SEQUENCE {
    id              INTEGER,
    type            Conn-Type-Enum,
    admin           BOOLEAN,
    name            UniversalString,
    description     UniversalString,

    -- Layers' parameters
    eth-if          Conn-Layer-eth-if,
    eth-port        Conn-Layer-eth-port,
    firewall        Conn-Layer-firewall,
    ip-dhcp         Conn-Layer-ip-dhcp,
    ip-ipcp         Conn-Layer-ip-ipcp,
    ip-static       Conn-Layer-ip-static,
    ppp             Conn-Layer-ppp

    -- Service separation
    pfpool          Service-Separation
}

Connection-Seq ::= SEQUENCE OF Connection-Item

Configuration ::= SEQUENCE {
  connection         Connection-Seq,
  ...
}

END
