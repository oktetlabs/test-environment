-- SPDX-License-Identifier: Apache-2.0
-- Copyright (C) 2005-2022 OKTET Labs Ltd. All rights reserved.

TE-NDN-DHCPv4
DEFINITIONS ::=
BEGIN

IMPORTS DATA-UNIT FROM TE-NDN-General;

IMPORTS Ip4Address FROM TE-NDN-Tcp-Ip;

EXPORTS DHCPv4-Option, DHCPv4-Message, DHCPv4-CSAP;

DHCPv4-Option ::=  IMPLICIT SEQUENCE {
    code    [0] DATA-UNIT{INTEGER(0..255)},
    length  [1] DATA-UNIT{INTEGER} OPTIONAL,
    value   [2] DATA-UNIT{OCTET STRING}
}

DHCPv4-Message ::= IMPLICIT SEQUENCE {
    op     [0] DATA-UNIT{INTEGER(0..255)} OPTIONAL,
    htype  [1] DATA-UNIT{INTEGER(0..255)} OPTIONAL,
    hlen   [2] DATA-UNIT{INTEGER(0..255)} OPTIONAL,
    hops   [3] DATA-UNIT{INTEGER(0..255)} OPTIONAL,
    xid    [4] DATA-UNIT{INTEGER} OPTIONAL,
    secs   [5] DATA-UNIT{INTEGER(0..65535)} OPTIONAL,
    flags  [6] DATA-UNIT{INTEGER(0..65535)} OPTIONAL,
    ciaddr [7] DATA-UNIT{Ip4Address} OPTIONAL,
    yiaddr [8] DATA-UNIT{Ip4Address} OPTIONAL,
    siaddr [9] DATA-UNIT{Ip4Address} OPTIONAL,
    giaddr[10] DATA-UNIT{Ip4Address} OPTIONAL,
    chaddr[11] DATA-UNIT{OCTET STRING (SIZE 16)} OPTIONAL,
    sname [12] DATA-UNIT{OCTET STRING (SIZE 64)} OPTIONAL,
    file  [13] DATA-UNIT{OCTET STRING (SIZE 128)} OPTIONAL,
    options SEQUENCE OF DHCPv4-Option OPTIONAL
}

DHCPv4-CSAP ::= IMPLICIT SEQUENCE {
    ...
}

END
