TE-NDN-Ethernet
DEFINITIONS ::=
BEGIN

IMPORTS DATA-UNIT FROM TE-NDN-General;

EXPORTS EthernetAddress, Ethernet-Header, Ethernet-CSAP;

EthernetAddress ::= IMPLICIT OCTET STRING (SIZE (6))


Ethernet-Header ::= IMPLICIT SEQUENCE { 
    dst-addr [1] DATA-UNIT{EthernetAddress} OPTIONAL,
    src-addr [2] DATA-UNIT{EthernetAddress} OPTIONAL,
    eth-type [3] DATA-UNIT{OCTET STRING (SIZE 2)}OPTIONAL,
    cfi      [4] INTEGER {false(0), true(1),} OPTIONAL,
    priority [5] DATA-UNIT{INTEGER(0..7)} OPTIONAL,
    vlan-id  [6] DATA-UNIT{INTEGER(0..4095)} OPTIONAL,
}

Ethernet-CSAP ::= IMPLICIT SEQUENCE { 
    device-id   [0] DATA-UNIT{UniversalString},
    local-addr  [1] DATA-UNIT{EthernetAddress} OPTIONAL,
    remote-addr [2] DATA-UNIT{EthernetAddress} OPTIONAL,
    eth-type    [3] DATA-UNIT{OCTET STRING (SIZE 2)}OPTIONAL, 
    cfi         [4] INTEGER {false(0), true(1),} OPTIONAL,
    priority    [5] DATA-UNIT{INTEGER(0..7)} OPTIONAL,
    vlan-id     [6] DATA-UNIT{INTEGER(0..4095)} OPTIONAL,
}

END
